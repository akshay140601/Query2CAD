import Part
import Sketcher

# Step 1: Create a new document
doc = App.newDocument()

# Step 2: Sketch a triangle with base sides of 25mm and an altitude of 50mm
sketch = doc.addObject("Sketcher::SketchObject", "Sketch")
sketch.addGeometry(Part.Line(App.Vector(0, 0, 0), App.Vector(25, 0, 0)))
sketch.addGeometry(Part.Line(App.Vector(25, 0, 0), App.Vector(12.5, 50, 0)))
sketch.addGeometry(Part.Line(App.Vector(12.5, 50, 0), App.Vector(0, 0, 0)))
doc.recompute()

# Step 3: Extrude the sketch to create a solid triangular prism
wire = FreeCAD.ActiveDocument.Sketch.Shape.Wires[0]
face = Part.Face(wire)
prism = face.extrude(FreeCAD.Vector(0, 0, 50))

# Step 4: Add any additional details or features to the prism as needed

# Step 5: Check the design and make any necessary adjustments

# Step 6: Finalize the design and save the CAD model
Part.show(prism)
