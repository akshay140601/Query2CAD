import Part
import math
from FreeCAD import Base

# Create a new document
App.newDocument("Tetrahedron")
App.setActiveDocument("Tetrahedron")
App.ActiveDocument = App.getDocument("Tetrahedron")
Gui.ActiveDocument = Gui.getDocument("Tetrahedron")

# Step 2: Sketch an equilateral triangle with side length of 20 mm
triangle_points = []
angle = 360 / 3  # Angle between each vertex of the triangle

# Calculate the points of the equilateral triangle
for i in range(3):
    x = 20 * math.cos(math.radians(i * angle))
    y = 20 * math.sin(math.radians(i * angle))
    triangle_points.append(Base.Vector(x, y, 0))

# Create the equilateral triangle wire
triangle_wire = Part.makePolygon(triangle_points)
triangle_face = Part.Face(triangle_wire)

# Step 3: Extrude the triangle to create a 3D pyramid
pyramid_solid = triangle_face.extrude(Base.Vector(0, 0, 20))

# Step 4: Create three more equilateral triangles on the faces of the pyramid
# Assuming the base triangle is at the bottom, the other three triangles will be on the faces of the pyramid

# Step 5: Connect the vertices of the triangles to create a tetrahedron
# The vertices of the tetrahedron will be the vertices of the base triangle and the apex of the pyramid

# Step 6: Check the dimensions and angles to ensure accuracy

# Step 7: Show the tetrahedron model generated
tetrahedron_solid = Part.Solid(pyramid_solid)  # Convert the pyramid to a solid
tetrahedron_solid = tetrahedron_solid.makeFillet(0.1)  # Close the sides by adding fillets
Part.show(tetrahedron_solid)
App.activeDocument().recompute()
Gui.activeDocument().activeView().viewAxometric()
Gui.SendMsgToActiveView("ViewFit")
