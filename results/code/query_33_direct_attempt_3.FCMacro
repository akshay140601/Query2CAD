import FreeCAD as App
import Part
import Sketcher

# Step 1: Create a new document
doc = App.newDocument()

# Step 2: Sketch the outline of the H-shaped beam
sketch = doc.addObject("Sketcher::SketchObject", "Sketch")
sketch.addGeometry(Part.LineSegment(App.Vector(-25, 0, 0), App.Vector(25, 0, 0)))
sketch.addGeometry(Part.LineSegment(App.Vector(-25, 50, 0), App.Vector(-25, -50, 0)))
sketch.addGeometry(Part.LineSegment(App.Vector(25, 50, 0), App.Vector(25, -50, 0)))
doc.recompute()

# Step 3: Extrude the sketch to create a solid body for the beam
beam = sketch.extrude(App.Vector(0, 0, 100))

# Step 4: Create additional sketches for any details or features required on the beam
# No additional details needed for H-shaped beam

# Step 5: No additional sketches to extrude

# Step 6: Verify the dimensions and appearance of the H-shaped beam
Part.show(beam)

# Step 7: Export the CAD design as a file for further use or analysis
doc.saveAs("H_Shaped_Beam.FCStd")
