import Part
from FreeCAD import Base

# Create a new document
App.newDocument("BentPipe")
App.setActiveDocument("BentPipe")
App.ActiveDocument = App.getDocument("BentPipe")
Gui.ActiveDocument = Gui.getDocument("BentPipe")

# Create the cylindrical pipe
cylinder = Part.makeCylinder(25, 50)  # Outer diameter of 50mm

# Create the torus for the bend
torus = Part.makeTorus(15, 30)  # Inner diameter of 30mm

# Fuse the cylindrical pipe and torus to create the bent pipe
bent_pipe = cylinder.fuse(torus)

# Show the 3D model of the bent pipe
Part.show(bent_pipe)
App.activeDocument().recompute()
Gui.activeDocument().activeView().viewAxometric()
Gui.SendMsgToActiveView("ViewFit")
